;;; TGIRR CAD LISP - VDNG: Ve day nho giot
(vl-load-com)
(defun c:VDNG (/ *error* old-layer old-osmode old-cmdecho old-filletrad mode radius distance selected side-point new-entity)
  (setq old-layer (getvar "CLAYER") old-osmode (getvar "OSMODE") old-cmdecho (getvar "CMDECHO") old-filletrad (getvar "FILLETRAD"))
  (defun TGIRR:VDNG-RESTORE ()
    (if old-layer (setvar "CLAYER" old-layer))
    (if old-osmode (setvar "OSMODE" old-osmode))
    (if old-cmdecho (setvar "CMDECHO" old-cmdecho))
    (if old-filletrad (setvar "FILLETRAD" old-filletrad)))
  (defun *error* (message)
    (TGIRR:VDNG-RESTORE)
    (vl-catch-all-apply 'vl-cmdf (list "_.UNDO" "_End"))
    (if (and message (not (wcmatch (strcase message) "*CANCEL*,*QUIT*,*BREAK*"))) (prompt (strcat "\nLỗi VDNG: " message)))
    (princ))
  (setvar "CMDECHO" 0)
  (vl-cmdf "_.UNDO" "_Begin")
  (if (not (tblsearch "LAYER" "TG-DRIP"))
    (vl-cmdf "_.-LAYER" "_Make" "TG-DRIP" "_Color" "34" "TG-DRIP" ""))
  (setvar "CLAYER" "TG-DRIP")
  (initget "TuDo Offset")
  (setq mode (getkword "\nChọn cách vẽ [TuDo/Offset] <TuDo>: "))
  (if (null mode) (setq mode "TuDo"))
  (cond
    ((= mode "TuDo")
      (setq radius (getdist "\nNhập bán kính bo cong góc <150>: "))
      (if (null radius) (setq radius 150.0))
      (prompt "\nChọn các điểm đi dây; nhấn Enter để kết thúc: ")
      (vl-cmdf "_.PLINE")
      (while (> (getvar "CMDACTIVE") 0) (vl-cmdf pause))
      (setq new-entity (entlast))
      (if new-entity (progn (setvar "FILLETRAD" radius) (vl-catch-all-apply 'vl-cmdf (list "_.FILLET" "_Polyline" new-entity)))))
    ((= mode "Offset")
      (setq distance (getdist "\nNhập khoảng cách rải dây: "))
      (if distance
        (progn (setq selected (entsel "\nChọn đường bao bồn cây: "))
          (if selected
            (progn (setq side-point (getpoint "\nChọn phía bên trong bồn để tạo dây: "))
              (if side-point
                (progn (vl-cmdf "_.OFFSET" distance selected side-point "") (setq new-entity (entlast))
                  (if new-entity (vl-cmdf "_.CHPROP" new-entity "" "_Layer" "TG-DRIP" "_Color" "BYLAYER" "_LWeight" "BYLAYER" ""))))))))))
  (TGIRR:VDNG-RESTORE)
  (vl-cmdf "_.UNDO" "_End")
  (prompt "\nHoàn tất lệnh VDNG.")
  (princ))
(prompt "\nTGIRR: Đã nạp lệnh VDNG - vẽ dây nhỏ giọt.")
(princ)
