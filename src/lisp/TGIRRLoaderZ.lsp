;;; TGIRR CAD - ZWCAD loader
;;; Nap cac lenh LISP va DLL .NET cho ZWCAD.
;;;
;;; Thu muc goc duoc xac dinh theo thu tu uu tien:
;;;   1. Bien global *TGIRR:ZW-ROOT* (dat bang lenh TGIRRSETDIR)
;;;   2. Bien moi truong TGIRR_CAD_DIR_Z (dat bang lenh TGIRRSETDIR)
;;;   3. Thu muc chua TGIRR.Zwcad.dll (findfile theo search path)
;;;   4. Thu muc chua chinh file loader nay (TGIRRLoaderZ.lsp)
;;;
;;; Loader viet phong thu: moi findfile/load deu nam trong vl-catch-all-apply
;;; va chi dung cac thu muc CO THAT, nen khong the hien loi roi kieu
;;; "undefined function - <duong dan>" khi duong dan khong hop le.
(vl-load-com)

;; Bo ky tu "\" o cuoi duong dan (vi du "C:\...\en-US\").
(defun TGIRR:TRIM-SLASH (dir / n)
  (if (and dir (setq n (strlen dir)) (> n 0) (= (substr dir n 1) "\\"))
    (substr dir 1 (1- n))
    dir))

;; findfile an toan - khong bao loi roi.
(defun TGIRR:FINDFILE-SAFE (file / r)
  (setq r (vl-catch-all-apply 'findfile (list file)))
  (if (vl-catch-all-error-p r) nil r))

;; Kiem tra thu muc co ton tai khong (an toan).
(defun TGIRR:DIR-EXISTS (dir / r)
  (setq r (vl-catch-all-apply 'vl-file-directory-p (list dir)))
  (and (not (vl-catch-all-error-p r)) r))

;; Xac dinh thu muc goc - KHONG dung ROAMABLEROOTPREFIX (de tranh duong dan bi loi).
(defun TGIRR:ZW-DIR (/ dll loader)
  (cond
    (*TGIRR:ZW-ROOT*)
    ((getenv "TGIRR_CAD_DIR_Z"))
    ((setq dll (TGIRR:FINDFILE-SAFE "TGIRR.Zwcad.dll"))
     (vl-filename-directory dll))
    ((setq loader (TGIRR:FINDFILE-SAFE "TGIRRLoaderZ.lsp"))
     (vl-filename-directory loader))
    (t nil)))

;; Danh sach thu muc ung vien - chi cac thu muc TON TAI, dang chuan hoa (khong \ cuoi).
(defun TGIRR:ZW-CANDIDATES (/ base parent lst d)
  (setq base (TGIRR:TRIM-SLASH (TGIRR:ZW-DIR)))
  (setq lst nil)
  (if base
    (progn
      (setq lst (list base))
      (setq parent (TGIRR:TRIM-SLASH (vl-filename-directory base)))
      ;; Lisp + Windows ngay duoi thu muc goc
      (foreach d (list (strcat base "\\Lisp") (strcat base "\\Windows"))
        (if (TGIRR:DIR-EXISTS d)
          (setq lst (cons d lst))))
      ;; Neu goc la \Lisp hoac \Windows thi them thu muc sibling
      (if (and parent (/= (strcase parent) (strcase base)))
        (foreach d (list (strcat parent "\\Lisp") (strcat parent "\\Windows"))
          (if (and (TGIRR:DIR-EXISTS d) (not (member d lst)))
            (setq lst (cons d lst)))))))
  (reverse lst))

;; Tim file trong cac thu muc ung vien; tra ve path day du hoac nil.
(defun TGIRR:ZW-FIND (name / result)
  (setq result nil)
  (foreach d (TGIRR:ZW-CANDIDATES)
    (if (and (not result) d)
      (setq result (TGIRR:FINDFILE-SAFE (strcat d "\\" name)))))
  result)

(defun TGIRR:ZW-LOAD-FILE (name / path result)
  (setq path (TGIRR:ZW-FIND name))
  (if path
    (progn
      (setq result (vl-catch-all-apply 'load (list path)))
      (if (vl-catch-all-error-p result)
        (prompt (strcat "\nTGIRR ZWCAD: LOAD lỗi " name " - " (vl-catch-all-error-message result)))
        (prompt (strcat "\nTGIRR ZWCAD: Đã nạp " path))))
    (prompt (strcat "\nTGIRR ZWCAD: Không tìm thấy " name))))

(defun TGIRR:ZW-NETLOAD (name / path result)
  (setq path (TGIRR:ZW-FIND name))
  (if path
    (progn
      ;; ZWCAD cần Enter kết thúc NETLOAD; nếu bỏ đối số rỗng, command stack
      ;; vẫn còn mở và loader tiếp theo thường trả về "Function cancelled".
      (setq result (vl-catch-all-apply '(lambda () (command "_.NETLOAD" path ""))))
      (if (vl-catch-all-error-p result)
        (prompt (strcat "\nTGIRR ZWCAD: NETLOAD lỗi " name " - " (vl-catch-all-error-message result)))
        (prompt (strcat "\nTGIRR ZWCAD: NETLOAD ok " path))))
    (prompt (strcat "\nTGIRR ZWCAD: Không tìm thấy DLL " name))))

;; Xếp lệnh mở Palette sau khi TGIRRLOAD kết thúc hẳn. Không dùng COMMAND
;; lồng trực tiếp vì ZWCAD còn đang ở command stack của NETLOAD.
(defun TGIRR:ZW-QUEUE-PALETTE (/ app doc result)
  (setq result
    (vl-catch-all-apply
      '(lambda ()
         (setq app (vlax-get-acad-object)
               doc (vla-get-ActiveDocument app))
         (vla-SendCommand doc "TGIRRPALETTE "))))
  (if (vl-catch-all-error-p result)
    (prompt "\nTGIRR ZWCAD: Hãy gõ TGIRRPALETTE để mở bảng công cụ.")))

;; Bat/tat nap tung goi LISP - doc %APPDATA%\TGIRR\load-settings.txt (lenh TGIRRSETTINGS).
(defun TGIRR:SETTINGS-FILE (/ appdata)
  (setq appdata (getenv "APPDATA"))
  (if (and appdata (> (strlen appdata) 0))
    (strcat appdata "\\TGIRR\\load-settings.txt")
    nil))

(defun TGIRR:SETTING-TOKENS (text / pos out tok)
  (setq out nil)
  (while (and text (setq pos (vl-string-search "," text)))
    (setq tok (substr text 1 pos)
          text (substr text (+ pos 2)))
    (if (> (strlen tok) 0) (setq out (cons tok out))))
  (if (and text (> (strlen text) 0)) (setq out (cons text out)))
  (reverse out))

;; Danh sach lenh bi tat (rong = nap tat ca).
(defun TGIRR:DISABLED-LIST (/ path fh line rest pos)
  (setq path (TGIRR:SETTINGS-FILE))
  (setq line nil)
  (if (and path (findfile path) (setq fh (open path "r")))
    (progn
      (setq line (read-line fh))
      (close fh)))
  (setq rest (if (and line (= (substr line 1 2) "v1")) (substr line 3) ""))
  (setq pos (vl-string-search "disabled=" rest))
  (if pos (TGIRR:SETTING-TOKENS (substr rest (+ pos 10))) nil))

(defun TGIRR:LOAD-ENABLED-P (id / disabled)
  (setq disabled (TGIRR:DISABLED-LIST))
  (not (member id disabled)))

;; Canh bao khi nguoi dung lo tat het moi lenh (CAD se "nhu khong chay").
(defun TGIRR:WARN-IF-ALL-OFF (/ disabled total)
  (setq disabled (TGIRR:DISABLED-LIST))
  (setq total (if *TGIRR:ALL-COMMANDS* (length *TGIRR:ALL-COMMANDS*) 0))
  (if (and (> total 0) (>= (length disabled) total))
    (prompt "\nTGIRR ZWCAD: TAT CA lenh dang bi tat trong TGIRRSETTINGS - go TGIRRSETTINGS de bat lai.")))

(defun TGIRR:ZW-LOAD-GROUP (name commands forms / disabled count)
  (setq disabled (TGIRR:DISABLED-LIST))
  (setq count 0)
  (foreach cmd commands
    (if (not (member cmd disabled)) (setq count (1+ count))))
  (if (> count 0)
    (TGIRR:ZW-LOAD-FILE name)
    (prompt (strcat "\nTGIRR ZWCAD: Bo qua " name " (tat toan bo lenh trong file).")))
  (if (> count 0)
    (foreach pair forms
      (if (member (car pair) disabled)
        (progn
          (vl-catch-all-apply 'eval (list (cadr pair)))
          (prompt (strcat "\nTGIRR ZWCAD: " (car pair) " da tat trong TGIRRSETTINGS.")))))))

;; Chay mot bieu thuc va bo qua loi: mot nhom hong khong duoc lam dung ca qua trinh nap.
(defun TGIRR:SAFE (expr / result)
  (setq result (vl-catch-all-apply 'eval (list expr)))
  (if (vl-catch-all-error-p result)
    (prompt (strcat "\nTGIRR ZWCAD: Bo qua mot nhom lenh - " (vl-catch-all-error-message result))))
  result)

(defun c:TGIRRLOAD (/ root)
  (setq root (TGIRR:ZW-DIR))
  (setq *TGIRR:ZW-ROOT* root)
  (if (not root)
    (progn
      (prompt "\nTGIRR ZWCAD: Chưa biết thư mục. Gõ TGIRRSETDIR để chọn file TGIRR.Zwcad.dll trước.")
      (princ))
    (progn
      ;; Nap cac lenh AutoLISP (moi nhom duoc bao loi rieng).
      (TGIRR:SAFE '(TGIRR:ZW-LOAD-GROUP "SBS.lsp" '("SBS" "SBSE" "SCH")
        '(("SBS" (setq C:SBS nil)) ("SBSE" (setq C:SBSE nil)) ("SCH" (setq C:SCH nil)))))
      (TGIRR:SAFE '(TGIRR:ZW-LOAD-GROUP "HBD.lsp" '("HBD" "JH" "SP2PL")
        '(("HBD" (setq C:HBD nil)) ("JH" (setq C:JH nil)) ("SP2PL" (setq C:SP2PL nil)))))
      (TGIRR:SAFE '(TGIRR:ZW-LOAD-GROUP "DOITEXT.lsp" '("DOITEXT" "DOIMTEXT")
        '(("DOITEXT" (setq C:DOITEXT nil)) ("DOIMTEXT" (setq C:DOIMTEXT nil)))))
      (TGIRR:SAFE '(TGIRR:ZW-LOAD-GROUP "KHO.lsp" '("KHO" "TENBV")
        '(("KHO" (setq C:KHO nil)) ("TENBV" (setq C:TENBV nil)))))
      (TGIRR:SAFE '(TGIRR:ZW-LOAD-GROUP "TGIRRBAR.lsp" '("TGIRRBAR")
        '(("TGIRRBAR" (setq C:TGIRRBAR nil)))))
      ;; Ten quen thuoc cua cac lenh .NET (TL, TGN, ...) - chi tao khi lenh con bat.
      (TGIRR:SAFE '(TGIRR:ZW-LOAD-FILE "TGIRRCOMMANDS.lsp"))
      (TGIRR:WARN-IF-ALL-OFF)
      ;; Nap plugin .NET (CPLUS, VDNG, TNET, TL, TGL, CVPL, TGN, TGIRRPALETTE)
      (TGIRR:ZW-NETLOAD "TGIRR.Zwcad.dll")
      ;; Không tự gọi command TGIRRPALETTE ngay trong lúc NETLOAD.
      ;; Một số bản ZWCAD còn giữ command stack của NETLOAD; gọi command lồng
      ;; tại đây sẽ khiến input bị chuyển thành "Needs a point or Last".
      ;; DLL đã được nạp; xếp Palette chạy sau khi loader kết thúc.
      (prompt "\nTGIRR ZWCAD: Đã nạp plugin, đang mở bảng công cụ...")
      (TGIRR:ZW-QUEUE-PALETTE)
      (prompt (strcat "\nTGIRR CAD cho ZWCAD: Thư mục gốc " root))
      (princ))))

(defun c:TGIRRSETDIR (/ f d)
  (setq f (getfiled "Chọn file TGIRR.Zwcad.dll để xác định thư mục" "" "dll" 0))
  (if f
    (progn
      (setq d (vl-filename-directory f))
      (setenv "TGIRR_CAD_DIR_Z" d)
      (setq *TGIRR:ZW-ROOT* d)
      (prompt (strcat "\nTGIRR ZWCAD: Đã đặt thư mục = " d "\n  Gõ TGIRRLOAD để nạp đầy đủ.")))
    (prompt "\nTGIRR ZWCAD: Hủy chọn thư mục."))
  (princ))

(prompt "\nTGIRR ZWCAD: Gõ TGIRRSETDIR để chỉ thư mục (1 lần), rồi TGIRRLOAD để nạp lệnh.")
(princ)
